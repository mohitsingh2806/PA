BE-ACU-MIB DEFINITIONS ::= BEGIN

        DisplayString ::= OCTET STRING

        BEL             OBJECT IDENTIFIER ::= { enterprises 29868 }

        MANPACK_TERMINAL            OBJECT IDENTIFIER ::= { BEL 1 }

      



        data_mptDescription OBJECT-TYPE
                SYNTAX OCTET STRING (SIZE (32))
                ACCESS read-only
                STATUS mandatory
                DESCRIPTION
                        "Description of the System"
                ::= { MANPACK_TERMINAL 1 }

        data_mptUpTime OBJECT-TYPE 
                SYNTAX INTEGER (0..4294967296)	
                ACCESS read-only
                STATUS mandatory
                DESCRIPTION
                        "System Up Time"
                ::= { MANPACK_TERMINAL 2 }

        data_mptLocation OBJECT-TYPE
                SYNTAX OCTET STRING (SIZE (19))
                ACCESS read-only
                STATUS mandatory
                DESCRIPTION
                        "Lat, Long Values of the system"
                ::= { MANPACK_TERMINAL 3 }

        data_mptBUCAttenuation OBJECT-TYPE
                SYNTAX OCTET STRING (SIZE (5))
                ACCESS read-write
                STATUS mandatory
                DESCRIPTION
                        "BUC Attenuation Level"
                ::= { MANPACK_TERMINAL 4 }

        data_mptBUCTxPower OBJECT-TYPE
               SYNTAX OCTET STRING (SIZE (5))		

                ACCESS read-only
                STATUS mandatory
                DESCRIPTION
                        "BUC Tx Power"
                ::= { MANPACK_TERMINAL 5 }

        data_Spare1 OBJECT-TYPE
                SYNTAX INTEGER (0..1)
                ACCESS read-only
                STATUS mandatory
                DESCRIPTION
                        "Spare Integer"
                ::= { MANPACK_TERMINAL 6 }

   




    END
